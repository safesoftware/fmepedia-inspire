FME workspace Validation.fmw

Parameters:
- SchemaFile = C:\PS\ArcheivedPresentations\InspireParis2013\schemas\GeographicalNames.xsd
- INSPIRGML = $(FME_MF_DIR)geographicNames.xml   # INSPIRE GML File

Readers:
- TEXTLINE_1: TEXTLINE from $(INSPIRGML)

Writers:
- TEXTLINE_2: TEXTLINE to $(FME_MF_DIR)Report.html

text_line (reader TEXTLINE_1)
    attributes: text_line_data buffer
    -> AttributeRenamer_3
AttributeRenamer_3
    ATTR_LIST = text_line_data,GMLFile,""
    -> XMLValidator
XMLValidator
    VAL_MODE_1 = Syntax and Schema
    SCHEMA_LOC = $(SchemaFile)
    XML_ATTR_TEXT = GMLFile
    LIST_NAME = _xml_error
    XML_INPUT_TYPE = Attribute Specifying XML Text
    LIMIT_ERRORS = No
    FAILED -> ListExploder
    PASSED -> FilenamePartExtractor_2

Bookmark: Make a Nice Report
FilenamePartExtractor_2
    SRC_ATTR = $(INSPIRGML)
    ROOTNAME_ATTR = File
    -> AttributeCreator_3
AttributeCreator_3
    ATTR_LIST = Type,File Passed Validation,LineNumber,-,Column,-,ErrorMessage,None
    -> XMLTemplater_3 [input 2]
ListExploder
    INDEX_ATTR = _element_index
    MODE = List Elements and Original Attributes
    LIST_ATTR = _xml_error{}
    LIST_FOUND -> AttributeRenamer
AttributeRenamer
    ATTR_LIST = type,Type,"",file,File,"",line,LineNumber,"",col,Column,"",desc,ErrorMessage,""
    -> FilenamePartExtractor
FilenamePartExtractor
    SRC_ATTR = $(INSPIRGML)
    FULLNAME_ATTR = File
    -> XMLTemplater_3 [input 2]
Creator
    COORDSYS = LL84
    NUM = 1
    GEOMTYPE = Geometry Object
    CREATED -> XMLTemplater_3 [input 1]
XMLTemplater_3
    RECORDS_QUERY_EXPR:
      <tr>
      <td>{fme:get-attribute("File")}</td>
      <td>{fme:get-attribute("Type")}</td>
      <td>{fme:get-attribute("LineNumber")}</td>
      <td>{fme:get-attribute("Column")}</td>
      <td>{fme:get-attribute("ErrorMessage")}</td>
      </tr>
    RESULT_ATTRIBUTE = text_line_data
    ROOT_QUERY_EXPR:
      <table class="gridtable">
      <tr><th>File</th><th>Type of Error</th><th>LineNumber</th><th>Column</th><th>ErrorMessage</th></tr>
      {fme:process-features("RECORDS")}
      </table>
    VISIBLE_QUERY_VALIDATE = Yes
    OUTPUT_XML_HEADER = No
    -> AttributeCreator
AttributeCreator
    ATTR_LIST:
      text_line_data,<HEAD>
      <style type="text/css">
      table.gridtable {
      	font-family: verdana,arial,sans-serif;
      	font-size:11px;
      	color:#333333;
      	border-width: 1px;
      	border-color: #666666;
      	border-collapse: collapse;
      }
      table.gridtable th {
      	border-width: 1px;
      	padding: 8px;
      	border-style: solid;
      	border-color: #666666;
      	background-color: #dedede;
      }
      table.gridtable td {
      	border-width: 1px;
      	padding: 8px;
      	border-style: solid;
      	border-color: #666666;
      	background-color: #CDFFFF;
      }
      </style>
      </HEAD>
      @Value(text_line_data)
    -> text_line (writer TEXTLINE_2)
text_line (writer TEXTLINE_2)
    attributes: text_line_data buffer
